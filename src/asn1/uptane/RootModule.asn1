RootModule DEFINITIONS AUTOMATIC TAGS ::= BEGIN

  EXPORTS RootMetadata, TopLevelRoles, TopLevelRole;

  IMPORTS Keyids,
          Length,
          PublicKeys,
          RoleType,
          Threshold,
          URLs FROM CommonModule;

  RootMetadata ::= SEQUENCE {
    numberOfKeys  Length,
    keys          PublicKeys,
    numberOfRoles Length,
    roles         TopLevelRoles
    -- https://tools.ietf.org/html/rfc6025#section-2.4.2
  }
  -- Adjust length of SEQUENCE OF to your needs.
  TopLevelRoles ::= SEQUENCE (SIZE(4)) OF TopLevelRole
  TopLevelRole  ::= SEQUENCE {
    role            RoleType,
    -- TAP 5: The URLs pointing to the metadata file for this role.
    numberOfURLs    Length OPTIONAL,
    urls            URLs OPTIONAL,
    numberOfKeyids  Length,
    keyids          Keyids,
    threshold       Threshold
  }

END
