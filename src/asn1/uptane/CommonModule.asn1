CommonModule DEFINITIONS AUTOMATIC TAGS ::= BEGIN

  EXPORTS ALL;

  RoleType        ::= ENUMERATED {root, targets, snapshot, timestamp}

  -- String types.
  Filename        ::= IA5String (SIZE(1..32))
  -- No known path separator allowed in a strict filename.
  StrictFilename  ::= IA5String (SIZE(1..32))
                                    (PATTERN "[^/\\]+")
  BitString       ::= BIT STRING    (SIZE(1..1024))
  OctetString     ::= OCTET STRING  (SIZE(1..1024))
  -- Adjust length of SEQUENCE OF to your needs.
  Paths           ::= SEQUENCE (SIZE(1..8)) OF Path
  Path            ::= IA5String (SIZE(1..32))
                                    (PATTERN "[\w\*\\/]+")
  -- Adjust length of SEQUENCE OF to your needs.
  URLs            ::= SEQUENCE (SIZE(0..8)) OF URL
  URL             ::= IA5String (SIZE(1..1024))
  -- A generic identifier for vehicles, primaries, secondaries.
  Identifier      ::= IA5String (SIZE(1..32))

  Natural         ::= INTEGER (0..MAX)
  Positive        ::= INTEGER (1..MAX)
  Length          ::= Positive
  Threshold       ::= Positive
  Version         ::= Positive
  -- The date and time in UTC encoded as a UNIX timestamp.
  UTCDateTime     ::= Positive

  BinaryData      ::= CHOICE {
    bitString     BitString,
    octetString   OctetString
  }

  -- Adjust length of SEQUENCE OF to your needs.
  Hashes          ::= SEQUENCE (SIZE(1..8)) OF Hash
  Hash            ::= SEQUENCE {
    function      HashFunction,
    digest        BinaryData
  }
  HashFunction ::= ENUMERATED {sha224, sha256, sha384, sha512, sha512-224,
                               sha512-256}

  -- Adjust length of SEQUENCE OF to your needs.
  Keyids          ::= SEQUENCE (SIZE(1..8)) OF Keyid
  -- Usually, a hash of a public key.
  Keyid           ::= BinaryData

  -- Adjust length of SEQUENCE OF to your needs.
  Signatures      ::= SEQUENCE (SIZE(1..8)) OF Signature
  Signature       ::= SEQUENCE {
    keyid         Keyid,
    method        SignatureMethod,
    -- For efficient checking, sign the hash of the message instead of the
    -- message itself.
    hash          Hash,
    -- The signature itself.
    value         BinaryData
  }
  SignatureMethod ::= ENUMERATED {rsassa-pss, ed25519}

  -- Adjust length of SEQUENCE OF to your needs.
  PublicKeys      ::= SEQUENCE (SIZE(1..8)) OF PublicKey
  PublicKey       ::= SEQUENCE {
    publicKeyid     Keyid,
    publicKeyType   PublicKeyType,
    publicKeyValue  BinaryData
  }
  PublicKeyType   ::= ENUMERATED {rsa, ed25519}

END
