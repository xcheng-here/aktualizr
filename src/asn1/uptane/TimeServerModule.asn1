TimeServerModule DEFINITIONS AUTOMATIC TAGS ::= BEGIN

  IMPORTS Length,
          Signatures,
          UTCDateTime FROM CommonModule;

  -- What a primary sends the time server: a token from each of its secondaries.
  SequenceOfTokens ::= SEQUENCE {
    numberOfTokens  Length,
    tokens          TimeTokens
  }
  -- Adjust length of SEQUENCE OF to your needs.
  TimeTokens  ::= SEQUENCE (SIZE(1..128)) OF TimeToken
  TimeToken   ::= INTEGER

  -- What the time server sends in response.
  CurrentTime   ::= SEQUENCE {
    signed              TimeTokensAndTimestamp,
    numberOfSignatures  Length,
    signatures          Signatures
  }
  TimeTokensAndTimestamp ::= SEQUENCE {
    numberOfTokens  Length,
    tokens          TimeTokens,
    timestamp       UTCDateTime
    -- https://tools.ietf.org/html/rfc6025#section-2.4.2
  }

END
