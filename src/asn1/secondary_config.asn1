SecondaryConfig DEFINITIONS AUTOMATIC TAGS ::= BEGIN

  IMPORTS Identifier,
          FileName,
          FilePath FROM Common;

  SecondaryConfig ::= SEQUENCE {
    secondaryType     SecondaryType,
    partialVerifying  BOOLEAN,
    ecuSerial         ECUSerial,
    ecuHardwareId     ECUHardwareId,

    fullClientDir     FilePath,
    ecuPrivateKey     FileName,
    ecuPublicKey      FileName,
    firmwarePath      FilePath,
    targetNamePath    FilePath,
    metadataPath      FilePath
  }

  SecondaryType ::= ENUMERATED {
    secVirtual,
    secLegacy,
    secUptane
  }

  ECUSerial ::= Identifier
  ECUHardwareId ::= Identifier

END
